module ietf-telemetry-message {
  yang-version 1.1;
  namespace "urn:ietf:params:xml:ns:yang:ietf-telemetry-message";
  prefix tm;

  import ietf-yang-types {
    prefix yang;
    reference
      "RFC 6991: Common YANG Data Types";
  }
  import ietf-inet-types {
    prefix inet;
  }
  import ietf-platform-manifest {
    prefix p-mf;
    reference
      "draft-ietf-opsawg-collected-data-manifest: A Data Manifest for
       Contextualized Telemetry Data";
  }

  organization
    "IETF Draft";
  contact
    "Author:    Ahmed Elhassany
                <mailto:ahmed.elhassany@swisscom.com>

                Thomas Graf
                <mailto:thomas.graf@swisscom.com>";
  description
    "This YANG modules defines a model for a telemetry collector to send
     collected YANG data from the network.

     Copyright (c) 2025 IETF Trust and the persons identified as
       authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2025-04-17 {
    description
      "Initial revision.";
    reference
      "RFC XXXX";
  }

  identity session-protocol {
    description
      "Base identity to represent session protocols.";
  }

  identity yp-push {
    base session-protocol;
    description
      "YANG-Push in RFC 8640 or RFC 8641 or RFC 8650.";
    reference
      "RFC 8640, RFC 8641, RFC 8650: YANG-Push Events and Notifications for Datastores.";
  }

  identity netconf {
    base session-protocol;
    description
      "NETCONF RPC as described in RFC 6241.";
    reference
      "RFC 6241: NETCONF RPC.";
  }

  identity restconf {
    base session-protocol;
    description
      "RESTCONF HTTP as described in RFC 8040.";
    reference
      "RFC 8040.";
  }

  typedef telemetry-notification-event-type {
    type enumeration {
      enum log {
        description
          "Collector is reporting the event as it arrived from the
           network element.";
      }
      enum update {
        description
          "
           Collector has updated an entry inside its local cache.
           This could be triggered by an event from the network for
           instance interface operational status changed or an internal
           event in the collector, such as a timer triggered to referesh
           old enteries.";
      }
      enum delete {
        description
          "Collector has deleted an entry from its local cache.";
      }
    }
    description
      "Type of event reported by the collector.";
  }

  typedef telemetry-session-protocol-type {
    type identityref {
      base session-protocol;
    }
    description
      "Notification protocol used to deliver the notification to the
       data collection.";
  }

  container message {
    config false;
    description
      "Telemetry message used in Data Mesh";
    leaf timestamp {
      type yang:date-and-time;
      mandatory true;
      description
        "Timestamp when the data collection collected the payload
         from the network element or an update or delete event is
         triggered.";
    }
    leaf session-protocol {
      type telemetry-session-protocol-type;
      mandatory true;
      description
        "Session protocol used to collect the payload of this message
         from the network";
    }
    container network-node-manifest {
      description
        "Address of network element from which the payload is collected.";
      uses p-mf:platform-details;
    }
    container data-collection-manifest {
      description
        "Address of the telemetry data collection.";
      uses p-mf:platform-details;
    }
    container telemetry-message-metadata {
      description
        "Extensible message and protocol specific metadata";
      leaf event-time {
        type yang:date-and-time;
        description
          "NETCONF eventTime. Redefined in here since NETCONF header is
           XML not YANG.";
      }
    }
    container data-collection-metadata {
      description
        "Metadata added by data collection.";
      leaf remote-address {
        type inet:host;
        mandatory true;
        description
          "Network node IP address.";
      }
      leaf remote-port {
        type inet:port-number;
        description
          "Network node transport port number.";
      }
      leaf local-address {
        type inet:host;
        description
          "Data collection IP address.";
      }
      leaf local-port {
        type inet:port-number;
        description
          "Data collection transport port number.";
      }
      list labels {
        key "name";
        description
          "Arbiterary labels assinged by the data collection.";
        leaf name {
          type string {
            length "1..max";
          }
          description
            "Label name.";
        }
        choice value {
          mandatory true;
          description
            "label value";
          choice string-choice {
            description
              "String value";
            leaf string-value {
              type string;
              description
                "String value";
            }
          }
          choice anydata-choice {
            description
              "YANG anydata value";
            anydata anydata-values {
              description
                "anydata yang";
            }
          }
        }
      }
    }
    anydata payload {
      description
        "Message or notification received from network element.";
    }
  }
}
