module ietf-yang-push-telemetry-message {
  yang-version 1.1;
  namespace "urn:ietf:params:xml:ns:yang:yang-push-telemetry-message";
  prefix yptm;

  import ietf-subscribed-notifications {
    prefix sn;
    reference
      "RFC 8639: Subscription to YANG Notifications";
  }
  import ietf-telemetry-message {
    prefix tm;
    reference
      "XXX";
  }
  import ietf-yang-push-revision {
    prefix ypr;
    reference
      "XXX";
  }

  organization
    "IETF Draft";
  contact
    "Author:    Ahmed Elhassany
                <mailto:ahmed.elhassany@swisscom.com>";
  description
    "Augments the ietf-telemetry-message with YANG Push specific
     fields.

     Copyright (c) 2024 IETF Trust and the persons identified as
       authors of the code.  All rights reserved.

     Redistribution and use in source and binary forms, with or without
     modification, is permitted pursuant to, and subject to the license
     terms contained in, the Revised BSD License set forth in Section
     4.c of the IETF Trust's Legal Provisions Relating to IETF Documents
     (https://trustee.ietf.org/license-info).

     This version of this YANG module is part of RFC XXXX; see the RFC
     itself for full legal notices.";

  revision 2024-02-20 {
    description
      "Initial revision.";
    reference
      "RFC XXXX";
  }

  augment "/tm:message/tm:session-metadata" {
    container yang-push-subscription {
      config false;
      leaf id {
        type sn:subscription-id;
        mandatory true;
        description
          "This references the affected subscription.";
      }
      container filters {
        description
          "Contains a list of configurable filters that can be applied to
            subscriptions.  This facilitates the reuse of complex filters
            once defined.";
        list stream-filter {
          key "name";
          description
            "A list of preconfigured filters that can be applied to
              subscriptions.";
          leaf name {
            type string;
            description
              "A name to differentiate between filters.";
          }
          uses sn:stream-filter-elements;
        }
      }
      uses ypr:yang-push-module-version-list;
    }
  }
}
